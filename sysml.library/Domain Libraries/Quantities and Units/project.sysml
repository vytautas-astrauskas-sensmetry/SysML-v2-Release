doc
/*
 * This library defines reusable and extensible model elements for physical quantities,
 * including vector and tensor quantities, quantity dimensions, measurement units, measurement scales, coordinate
 * frames, coordinate transformations and vector spaces.
 */

standard library extern package ISQ;
standard library extern package MeasurementReferences;
standard library extern package Quantities;
standard library extern package QuantityCalculations;
standard library extern package SI;
standard library extern package TensorCalculations;
standard library extern package Time;
standard library extern package <USCU> USCustomaryUnits;
standard library extern package VectorCalculations;
