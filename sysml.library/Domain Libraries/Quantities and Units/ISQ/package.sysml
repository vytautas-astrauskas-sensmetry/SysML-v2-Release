doc
/*
    * International system of quantities (ISQ), as defined in ISO/IEC 80000
    */

public extern package Base;                  // ISO/IEC 80000 base quantities and general concepts
public extern package SpaceTime;             // ISO 80000-3 "Space and Time"
public extern package Mechanics;             // ISO 80000-4 "Mechanics"
public extern package Thermodynamics;        // ISO 80000-5 "Thermodynamics"
public extern package Electromagnetism;      // IEC 80000-6 "Electromagnetism"
public extern package Light;                 // ISO 80000-7 "Light"
public extern package Acoustics;             // ISO 80000-8 "Acoustics"
public extern package ChemistryMolecular;    // ISO 80000-9 "Physical chemistry and molecular physics"
public extern package AtomicNuclear;         // ISO 80000-10 "Atomic and nuclear physics"
public extern package CharacteristicNumbers; // ISO 80000-11 "Characteristic numbers"
public extern package CondensedMatter;       // ISO 80000-12 "Condensed matter physics"
public extern package Information;           // IEC 80000-13 "Information science and technology"
public extern package Temperature;
