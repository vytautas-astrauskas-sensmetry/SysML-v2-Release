/* Additional quantity declarations */

private import ScalarValues::Real;
private import Quantities::*;
private import MeasurementReferences::*;

attribute def TemperatureDifferenceValue :> ScalarQuantityValue {
    doc
    /*
        * temperature difference
        * A separate temperature difference quantity and unit are needed in order to support °C, °F and centrigrade temperature differences
        */
    attribute :>> num: Real;
    attribute :>> mRef: TemperatureDifferenceUnit[1];
}

attribute temperatureDifference: TemperatureDifferenceValue [*] nonunique :> scalarQuantities;

attribute def TemperatureDifferenceUnit :> SimpleUnit {
    private attribute thermodynamicTemperaturePF: QuantityPowerFactor[1] { :>> quantity = isq.'Θ'; :>> exponent = 1; }
    attribute :>> quantityDimension { :>> quantityPowerFactors = thermodynamicTemperaturePF; }
}
